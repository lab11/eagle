/*
 *  This EAGLE User Language Program creates a CSV file for placing surface
 *  mount components.
 */

 #usage "Create Centroid file."

string Version = "1.3.0";  // Version 1.3,  August 12, 2013
string fileMessage;

string rotation(real Angle) {
  string s;
  sprintf(s, "%.1f", Angle);
  int pos = strchr(s, '.');
  if (pos >= 0) if (s[pos + 1] == '0') s[pos] = 0;
  return s;
}

string side(int Mirror) {
  string s;

  if (Mirror){
    s = "Bottom";
  }
  else {
    s = "Top";
  }
  return s;
}

if (!board) {
  dlgMessageBox("<hr><b>ERROR: This ULP will only operate in the board layout view.</b></hr><p>Switch to the board layout editor and re-run.");
  exit(1);
}

if (board) board(B) {
  output(filesetext(B.name, ".centroid")) {
    printf("# SMD component position file.\n");
    printf("# Created by centroid_smd.ulp %s.\n\n", Version);
    printf("# Centroid Data for pc board: \"%s\" as of: %s\n", filename(B.name), t2string(time()));
    printf("# Measurements are in inches.\n");
    printf("# Comma delimited.\n");
    printf("# Only surface mount components included.\n\n");
    printf("%s,%s,%s,%s,%s\n", "RefDes", "Layer", "LocationX", "LocationY", "Rotation");
    B.elements(E) {
      int isSmd;
      isSmd = 0;
      E.package.contacts(C) { if (C.smd) isSmd = 1; }
      if (isSmd) printf("%s,%s,%5.5f,%5.5f,%s\n", E.name, side(E.mirror), u2inch(E.x), u2inch(E.y), rotation(E.angle));
    }
  }
}
